CWY-GPS-MIB DEFINITIONS ::= BEGIN

IMPORTS
    OBJECT-GROUP FROM SNMPv2-CONF
    enterprises, Integer32, OBJECT-TYPE, MODULE-IDENTITY FROM SNMPv2-SMI;

-- ********************************************************************
-- *  MODULE IDENTITY
-- ********************************************************************
    gpsMib MODULE-IDENTITY
              LAST-UPDATED "202301251200Z"
              ORGANIZATION "CELERWAY"
              CONTACT-INFO "l.baj@celerway.com"
              DESCRIPTION
                  "MIB module for GPS info"
              REVISION "202301251200Z"
              DESCRIPTION
                  "First version"
        ::= { celerway 4 }

-- The Enterprises Number
    celerway OBJECT IDENTIFIER ::= { enterprises 55404 }

-- **********************************************************************
-- *  Table
-- **********************************************************************
    gpsInfoTable OBJECT-TYPE
        SYNTAX SEQUENCE OF GpsInfoEntry
        MAX-ACCESS not-accessible
        STATUS current
        DESCRIPTION
            "Modems info table"
        ::= { gpsMib 1 }

    gpsInfoEntry OBJECT-TYPE
        SYNTAX GpsInfoEntry
        MAX-ACCESS not-accessible
        STATUS current
        DESCRIPTION
            "An entry in the gpsInfoTable"
        INDEX { gpsInfoId }
        ::= { gpsInfoTable 1 }

    GpsInfoEntry ::=
    SEQUENCE {
        gpsInfoId Integer32,
        gpsSignal Integer32,
        gpsAge Integer32,
        gpsLatitude OCTET STRING,
        gpsLongitude OCTET STRING,
        gpsElevation OCTET STRING,
        gpsSpeed OCTET STRING,
        gpsSatellites Integer32
    }

    gpsInfoId OBJECT-TYPE
        SYNTAX Integer32 (1..512)
        MAX-ACCESS not-accessible
        STATUS current
        DESCRIPTION
            "GPS info ID"
        ::= { gpsInfoEntry 1 }


    gpsSignal OBJECT-TYPE
        SYNTAX Integer32
        MAX-ACCESS read-only
        STATUS current
        DESCRIPTION
            "GPS signal availability flag"
        ::= { gpsInfoEntry 2 }

    gpsAge OBJECT-TYPE
        SYNTAX Integer32
        MAX-ACCESS read-only
        STATUS current
        DESCRIPTION
            "Age of the GPS info in seconds"
        ::= { gpsInfoEntry 3 }

    gpsLatitude OBJECT-TYPE
        SYNTAX OCTET STRING
        MAX-ACCESS read-only
        STATUS current
        DESCRIPTION
            "GPS latitude"
        ::= { gpsInfoEntry 4 }

    gpsLongitude OBJECT-TYPE
        SYNTAX OCTET STRING
        MAX-ACCESS read-only
        STATUS current
        DESCRIPTION
            "GPS longitude"
        ::= { gpsInfoEntry 5 }

    gpsElevation OBJECT-TYPE
        SYNTAX OCTET STRING
        MAX-ACCESS read-only
        STATUS current
        DESCRIPTION
            "GPS elevation"
        ::= { gpsInfoEntry 6 }

    gpsSpeed OBJECT-TYPE
        SYNTAX OCTET STRING
        MAX-ACCESS read-only
        STATUS current
        DESCRIPTION
            "GPS Speed"
        ::= { gpsInfoEntry 7 }

    gpsSatellites OBJECT-TYPE
        SYNTAX Integer32
        MAX-ACCESS read-only
        STATUS current
        DESCRIPTION
            "Number of GPS sattelites"
        ::= { gpsInfoEntry 8 }

-- **********************************************************************
-- *  Object Group
-- **********************************************************************
    gpsInfoGroup OBJECT-GROUP
        OBJECTS {
            gpsSignal,
            gpsAge,
            gpsLatitude,
            gpsLongitude,
            gpsElevation,
            gpsSpeed,
            gpsSatellites
        }
        STATUS current
        DESCRIPTION
            "A collection of objects for GPS information."
        ::= { gpsMib 2 }


    gpsMibCompliance MODULE-COMPLIANCE
        STATUS current
        DESCRIPTION
            "Compliance statement for GPS MIB."
        MODULE
            MANDATORY-GROUPS { gpsInfoGroup }
        ::= { gpsMib 3 }
END
