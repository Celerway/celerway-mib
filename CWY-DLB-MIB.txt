CWY-DLB-MIB DEFINITIONS ::= BEGIN

IMPORTS
    OBJECT-GROUP, MODULE-COMPLIANCE FROM SNMPv2-CONF
    enterprises, Integer32, OBJECT-TYPE, MODULE-IDENTITY FROM SNMPv2-SMI;

-- ********************************************************************
-- *  MODULE IDENTITY
-- ********************************************************************
    loadBalancerMib MODULE-IDENTITY
              LAST-UPDATED "202009031200Z"
              ORGANIZATION "CELERWAY"
              CONTACT-INFO "l.baj@celerway.com"
              DESCRIPTION
                  "Add load balancer values"
              REVISION "202009031200Z"
              DESCRIPTION
                  "MIB module for Celerway load balancer subsystem"
        ::= { celerway 2 }

-- The Enterprises Number
    celerway OBJECT IDENTIFIER ::= { enterprises 55404 }

-- **********************************************************************
-- *  Table
-- **********************************************************************
    loadBalancerInfoTable OBJECT-TYPE
        SYNTAX SEQUENCE OF LoadBalancerInfoEntry
        MAX-ACCESS not-accessible
        STATUS current
        DESCRIPTION
            "Modems info table"
        ::= { loadBalancerMib 1 }

    loadBalancerInfoEntry OBJECT-TYPE
        SYNTAX LoadBalancerInfoEntry
        MAX-ACCESS not-accessible
        STATUS current
        DESCRIPTION
            "An entry in the loadBalancerInfoTable"
        INDEX { loadBalancerInfoId }
        ::= { loadBalancerInfoTable 1 }

    LoadBalancerInfoEntry ::=
    SEQUENCE {
        loadBalancerInfoId Integer32,
        interfaceName OCTET STRING,
        connectivityPassed OCTET STRING,
        linkQuality OCTET STRING
    }

    loadBalancerInfoId OBJECT-TYPE
        SYNTAX Integer32 (1..65535)
        MAX-ACCESS not-accessible
        STATUS current
        DESCRIPTION
            "Load balancer info ID"
        ::= { loadBalancerInfoEntry 1 }

    interfaceName OBJECT-TYPE
        SYNTAX OCTET STRING
        MAX-ACCESS read-only
        STATUS current
        DESCRIPTION
            "Name of the interface of the load balancer link"
    ::= { loadBalancerInfoEntry 2 }

    connectivityPassed OBJECT-TYPE
        SYNTAX OCTET STRING
        MAX-ACCESS read-only
        STATUS current
        DESCRIPTION
            "Status of the connectivity check for the load balancer link"
    ::= { loadBalancerInfoEntry 3 }

    linkQuality OBJECT-TYPE
        SYNTAX OCTET STRING
        MAX-ACCESS read-only
        STATUS current
        DESCRIPTION
            "Estimated link quality"
    ::= { loadBalancerInfoEntry 4 }

-- **********************************************************************
-- *  Object Group
-- **********************************************************************
    loadBalancerGroup OBJECT-GROUP
        OBJECTS { interfaceName, connectivityPassed, linkQuality }
        STATUS  current
        DESCRIPTION
            "A collection of objects for load balancer"
        ::= { loadBalancerMib 2 }

-- **********************************************************************
-- *  Module Compliance
-- **********************************************************************
    loadBalancerCompliance MODULE-COMPLIANCE
        STATUS  current
        DESCRIPTION
            "Compliance statement for load balancer MIB"
        MODULE
            MANDATORY-GROUPS { loadBalancerGroup }
        ::= { loadBalancerMib 3 }
END
